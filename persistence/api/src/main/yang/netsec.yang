module netsec {
    yang-version 1.1;
    namespace "urn:opendaylight:params:xml:ns:yang:netsec";
    prefix "netsec";

    revision "2018-09-01" { // TODO change revision to date of model creation
        description "Initial revision of netsec model";
    }
}
