module netsec-flow {
    yang-version 1;
    namespace "urn:opendaylight:packet:netsec";
    prefix netsec;

    import ietf-yang-types {prefix yang; revision-date 2013-07-15;}

    revision 2018-09-11 {
        description
            "Netsec packet module.";
    }

    grouping netsec-flow-fields {

        leaf id {
            type uint16;
            description "ID na base de dados";
        }

        leaf ether-type {
            type uint16;
            description "";
        }

        leaf flow-name {
            type string;
            description "";
        }

        leaf in-port {
            type string;
            description "";
        }

        leaf out-port {
            type string;
            description "";
        }

        leaf src-ipv4 {
            type string;
            description "";
        }

        leaf dst-ipv4 {
            type string;
            description "";
        }

        leaf src-mac {
            type string;
            description "";
        }

        leaf dst-mac {
            type string;
            description "";
        }

        leaf src-port {
            type uint16;
            description "";
        }

        leaf dst-port {
            type uint16;
            description "";
        }

        leaf income-date-time {
            type string;
            description "Data de chegada do pacote";
        }

        leaf ingress-port {
            type instance-identifier;
            description "Packet ingress port";
        }
        
        leaf duration-seconds{
            type uint32;
            description "";
        }
        leaf duration-nano-seconds{
            type uint32;
            description "";
        }
        leaf packet-count{
            type uint32;
            description "";
        }
        leaf byte-count{
            type uint32;
            description "";
        }

    }

    notification netsec-flow-received {
        uses netsec-flow-fields;
    }
}
