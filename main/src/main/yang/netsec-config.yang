module netsec-config {

    yang-version 1.1;
    namespace "urn:opendaylight:netsec:netsec-config";
    prefix "netsec-config";

    description
        "This module contains the base configuration for main implementation.";

    revision "2018-09-01" {
        description "Initial revision of netsec model";
    }

    container netsec-config {
        leaf is-learning-only-mode {
            type boolean;
            default false;
        }
        leaf is-install-dropall-flow {
            type boolean;
            default true;
        }
        leaf dropall-flow-table-id {
            type uint8;
            default 0;
        }
        leaf dropall-flow-priority {
            type uint16;
            default 0;
        }
        leaf dropall-flow-hard-timeout {
            type uint16;
            default 0;
        }
        leaf dropall-flow-idle-timeout {
            type uint16;
            default 0;
        }
        leaf reactive-flow-table-id {
            type uint8;
            default 0;
        }
        leaf reactive-flow-priority {
            type uint16;
            default 10;
        }
        leaf reactive-flow-hard-timeout {
            type uint16;
            default 300;
        }
        leaf reactive-flow-idle-timeout {
            type uint16;
            default 600;
        }
        leaf handler-packet-count-purge {
            type uint16;
            default 600;
        }
        leaf handler-max-buffer-time {
            type uint16;
            default 60000;
        }
        leaf collection-interval {
            type uint32;
            default 300000;
        }
    }
}
