module handler-config {

    yang-version 1.1;
    namespace "urn:opendaylight:netsec:handler-config";
    prefix "netsec-config";

    description
        "This module contains the base configuration for main implementation.";

    revision "2018-09-01" {
        description "Initial revision of netsec handler model";
    }

    container handler-config {
        leaf max-buffer-time {
            type uint16;
            default 60000;
        }
        leaf packet-count-purge {
            type uint16;
            default 100;
        }
    }
}
