module netsec-packet {
    yang-version 1;
    namespace "urn:opendaylight:packet:netsec";
    prefix netsec;

    import ietf-yang-types {prefix yang; revision-date 2013-07-15;}

    revision 2018-09-11 {
        description
            "Netsec packet module.";
    }

    grouping netsec-packet-fields {

        leaf id {
            type uint16;
            description "ID na base de dados";
        }

        leaf ether-type {
            type uint16;
            description "Tipo de pacote";
        }

        leaf flow-name {
            type string;
            description "Tipo de pacote";
        }

        leaf in-port {
            type string;
            description "Tipo de pacote";
        }

        leaf out-port {
            type string;
            description "Tipo de pacote";
        }

        leaf src-ipv4 {
            type string;
            description "Tipo de pacote";
        }

        leaf dst-ipv4 {
            type string;
            description "Tipo de pacote";
        }

        leaf src-mac {
            type string;
            description "Tipo de pacote";
        }

        leaf dst-mac {
            type string;
            description "Tipo de pacote";
        }

        leaf src-port {
            type uint16;
            description "Tipo de pacote";
        }

        leaf dst-port {
            type uint16;
            description "Tipo de pacote";
        }

        leaf income-date-time {
            type string;
            description "Data de chegada do pacote";
        }

        leaf ingress-port {
            type instance-identifier;
            description "Packet ingress port";
        }

    }

    notification netsec-packet-received {
        uses netsec-packet-fields;
    }
}
